# Brakes

# Specification: Brakes

## BRK-1: Braking
The brake shall stop the car within 40 m at 100 km/h.
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- Priority: high

### BRK-2: Wet road
On a wet road the brake shall stop the car within 60 m.
- Priority: low

## BRK-3: Parking brake
The parking brake shall hold the car on a slope of 20 %.
